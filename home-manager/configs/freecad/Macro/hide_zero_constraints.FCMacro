# Credits: https://forum.freecadweb.org/viewtopic.php?t=40385 in heavily modified
import FreeCAD
__title__="Macro_HideZeroConstraints"
__author__ = "aster94"
__url__     = "https://github.com/aster94"
__version__ = "0.0.1"
__date__    = "26/10/2019"

try:
	sk = Gui.ActiveDocument.getInEdit().Object # instanciate sketch itself for future use
	valid_constraints = ['Diameter', 'Radius', 'Angle', 'Distance']
	constraints = list(sk.Constraints) # to be checked but I think '.Constraints' already returns a list

	for cnt, constraint in enumerate(constraints):
		if any([c in str(constraint) for c in valid_constraints]) and constraint.Value == 0.0:
			sk.setVirtualSpace(cnt, True) # Hide
		
except Exception:
    pass # instead of 'None'
