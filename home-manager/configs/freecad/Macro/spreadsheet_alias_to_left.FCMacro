# -*- coding: utf-8 -*-

# Macro Begin: spreadsheet_alias_to_left.FCMacro +++++++++++++++++++++++++++++++
import FreeCAD
__title__="Macro_SpreadsheetAliasToTheLeft"
__author__ = "7FM"
__url__     = "https://github.com/7FM"
__version__ = "0.0.1"

doc = App.ActiveDocument
ss = doc.Spreadsheet
a = ord('B')

for i in range(1, 50):
  cellalias = ss.getAlias(chr(a) + str(i))  
  if not cellalias:  # write alias string to left cell
    name = ss.getContents(chr(a-1) + str(i)) 
    if name:  # write alias string to left cell
      # Since FreeCAD 0.21.1 the name starts with a ' character, we need to remove it!
      if len(name) > 1 and name[0] == "'":
        name = name[1:]
      ss.setAlias(chr(a) + str(i), name)
    else:
      break
  unit = ss.getDisplayUnit(chr(a) + str(i))
  if not unit:
    ss.setDisplayUnit(chr(a) + str(i), 'mm')

doc.recompute()
# Macro End: spreadsheet_alias_to_left.FCMacro +++++++++++++++++++++++++++++++++
